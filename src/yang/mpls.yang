submodule mpls {
  yang-version 1.1;
  belongs-to topology { prefix topology; }

  import tailf-ncs { prefix ncs; }

  grouping mpls-service-grouping {
    list mpls {
      key igp;
      leaf igp {
        type leafref {
          path "/topologies/igp/name";
        }
      }

      uses ncs:service-data;
      ncs:servicepoint mpls;

      uses mpls-grouping;
    }
  }

  grouping mpls-grouping {
    leaf ldp {
      type empty;
    }
    leaf rsvp {
      type empty;
    }
    container traffic-engineering {
      presence true;
      leaf pce {
        type empty;
      }
    }
  }
}
