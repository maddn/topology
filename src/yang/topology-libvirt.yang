submodule topology-libvirt {
  yang-version 1.1;
  belongs-to topology { prefix topology; }

  import tailf-common { prefix tailf; }

  include topology-base;

  // Additional groupings are in a seperate submodule due to an NSO bug.
  // If the groupings are in the same submodule they are missing from the
  // compiled moduled.
  include topology-libvirt-subgroupings;

  grouping topology-libvirt-grouping {
    uses topology-base-grouping {
      refine "topology/links/link/a-end-interface-id" {
        config false;
        tailf:cdb-oper {
          tailf:persistent true;
        }
      }
      refine "topology/links/link/z-end-interface-id" {
        config false;
        tailf:cdb-oper {
          tailf:persistent true;
        }
      }

      augment "topology" {
        container libvirt {
          leaf hypervisor {
            type leafref {
              path "/topologies/libvirt/hypervisor/name";
            }
          }
          action define {
            tailf:actionpoint libvirt-action;
            input {
              uses libvirt-action-input-grouping;
            }
            output {
              uses libvirt-action-output-grouping;
            }
          }
          action undefine {
            tailf:actionpoint libvirt-action;
            input {
              uses libvirt-action-input-grouping;
            }
            output {
              uses libvirt-action-output-grouping;
            }
          }
          action start {
            tailf:actionpoint libvirt-action;
            input {
              uses libvirt-action-input-grouping;
            }
            output {
              uses libvirt-action-output-grouping;
            }
          }
          action stop {
            tailf:actionpoint libvirt-action;
            input {
              uses libvirt-action-input-grouping;
            }
            output {
              uses libvirt-action-output-grouping;
            }
          }
        }

        action check-topology-status {
          tailf:actionpoint check-topology-status;
          input {
            leaf frequency {
              type enumeration {
                enum run-now;
                enum schedule;
              }
              default run-now;
            }
          }
          output {
            list device {
              leaf name {
                type string;
              }
              leaf status {
                type status;
              }
            }
          }
        }
        leaf status {
          type status;
          default undefined;
          config false;
          tailf:cdb-oper {
            tailf:persistent true;
          }
        }
      }

      augment "topology/links/link" {
        uses libvirt-network-grouping;
      }
      augment "topology/networks/network" {
        uses libvirt-network-grouping;
      }
      augment "topology/devices/device" {
        uses libvirt-device-grouping;
      }
    }
  }
}
