submodule libvirt {

  yang-version 1.1;

  belongs-to topology {
    prefix topology;
  }

  import ietf-yang-types {
     prefix yang;
  }
  import ietf-inet-types {
    prefix inet;
  }
  import tailf-common {
    prefix tailf;
  }
  import tailf-ncs {
    prefix ncs;
  }
  import tailf-ncs-ned {
    prefix ned;
  }

  grouping libvirt-get-network-grouping {
    leaf name {
      type string;
    }
    list interface {
      leaf domain-name {
        type string;
      }
      leaf host-interface {
        type string;
      }
    }
  }

  grouping libvirt-hypervisor-grouping {
    container libvirt {
      list hypervisor {
        key name;
        leaf name {
          type string;
        }
        leaf url {
          type string;
          mandatory true;
        }
        leaf username {
          type string;
        }
        leaf password {
          type string;
        }
        container management-network {
          leaf bridge {
            type string;
            default 'l3v1';
          }
          leaf ip-address-start {
            type inet:ipv4-address;
            default '198.18.1.60';
          }
          leaf gateway-address {
            type inet:ipv4-address;
            default '198.18.1.1';
          }
          leaf dns-server-address {
            type inet:ipv4-address;
            default '198.18.133.1';
          }
        }
        leaf mac-address-start {
          type yang:hex-string {
            tailf:value-length 3;
          }
          default '02:c1:5c';
        }

        container get {
          action domains {
            tailf:actionpoint libvirt-get-objects;
            output {
              list domain {
                leaf name {
                  type string;
                }
                leaf vcpus {
                  type uint16;
                }
                leaf memory {
                  type uint16;
                }
                leaf active {
                  type boolean;
                }
              }
            }
          }

          action networks {
            tailf:actionpoint libvirt-get-objects;
            output {
              list network {
                uses libvirt-get-network-grouping;
                leaf bridge-name {
                  type string;
                }
              }
              list external-bridge {
                uses libvirt-get-network-grouping;
              }
            }
          }

          action volumes {
            tailf:actionpoint libvirt-get-objects;
            output {
              list storage-pool {
                leaf name {
                  type string;
                }
                list volume {
                  leaf name {
                    type string;
                  }
                  leaf capacity {
                    type uint32;
                  }
                  leaf allocation {
                    type uint32;
                  }
                }
              }
            }
          }
        }
      }

      list device-definition {
        key name;
        leaf name {
          type string;
        }
        leaf device-type {
          type enumeration {
            enum XRv-9000;
            enum Generic;
          }
          mandatory true;
        }
        leaf vcpus {
          type uint16;
          mandatory true;
        }
        leaf memory {
          type uint16;
          mandatory true;
        }
        leaf template {
          type string;
          mandatory true;
        }
        leaf storage-pool {
          type string;
          mandatory true;
        }
        leaf base-image {
          type string;
          mandatory true;
        }
        leaf base-image-type {
          type enumeration {
            enum backing-store;
            enum clone;
          }
          default backing-store;
        }
        leaf disk-size {
          type uint16;
        }
        leaf day0-file {
          type string;
        }
        leaf day0-upload-file {
          type string;
        }
        leaf authgroup {
          type leafref {
            path "/ncs:devices/ncs:authgroups/ncs:group/ncs:name";
          }
          mandatory true;
        }
        leaf ned-id {
          //type union {
          //  type string;
            type identityref {
              base ned:cli-ned-id;
            }
          //}
        }
      }
    }
  }
}
