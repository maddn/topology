module topology {
  yang-version 1.1;
  namespace "http://example.com/topology";
  prefix topology;

  import tailf-common { prefix tailf; }
  import tailf-ncs { prefix ncs; }

  include topology-base;
  include topology-libvirt;
  include topology-libvirt-subgroupings;
  include libvirt;
  include ip-connectivity;
  include base-config;
  include igp;
  include bgp;
  include mpls;
  include segment-routing;
  include traffic-generator;
  include managed-topology-nano-plan;

  grouping hidden-topology-link {
    leaf topology {
      type leafref {
        path "/topologies/topology/name";
      }
      tailf:link "/topologies/topology[name=current()/../../topology]/name";
      tailf:hidden full;
      config false;
    }
  }

  container topologies {
    uses topology-libvirt-grouping;
    uses libvirt-hypervisor-grouping;
    uses base-config-service-grouping;
    uses igp-service-grouping;
    uses bgp-service-grouping;
    uses mpls-service-grouping;
    uses segment-routing-service-grouping;
    uses traffic-generator-service-grouping;
    uses managed-topology;
  }

  augment "/topologies/topology" {
    uses ip-connectivity-service-grouping;
  }

  grouping managed-topology {
    list managed-topology {
      key topology;

      ncs:servicepoint managed-topology;
      uses ncs:service-data;
      uses ncs:nano-plan-data;

      uses ip-connectivity-grouping;
      uses base-config-grouping;

      container igp {
        uses hidden-topology-link;
        uses igp-grouping;
      }
      container bgp {
        uses hidden-topology-link;
        uses bgp-grouping;
      }
      container mpls {
        when "../igp/name";
        uses mpls-grouping;
      }
      container segment-routing {
        when "../igp/name";
        uses segment-routing-grouping;
        container srv6 {
          when "../../ipv6";
          presence true;
          uses srv6-grouping;
        }
      }
      container traffic-generator {
        uses hidden-topology-link;
        uses traffic-generator-grouping;
      }
    }
  }

}
