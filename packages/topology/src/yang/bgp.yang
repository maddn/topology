submodule bgp {
  yang-version 1.1;
  belongs-to topology { prefix topology; }

  import tailf-common { prefix tailf; }
  import tailf-ncs { prefix ncs; }

  include ip-connectivity;

  description
    "This submodule contains the BGP service which will configure BGP
     neighbours based on their role.";

  grouping bgp-routers-grouping {
    leaf loopback-id {
      type uint8;
      tailf:non-strict-leafref {
        path "deref(../../topology)/.." +
             "/ip-connectivity/loopback-interfaces/loopback/id";
      }
      tailf:info
        "The IP address of this interface will be the neighbour address.";
    }
    leaf-list routers {
      type string;
      tailf:non-strict-leafref {
        path "deref(../../topology)/../devices/device/device-name";
      }
    }
  }

  grouping bgp-service-grouping {
    list bgp {
      key as-number;

      uses ncs:service-data;
      ncs:servicepoint bgp;

      leaf topology {
        type leafref {
          path "/topologies/topology/name";
        }
        mandatory true;
      }
      uses bgp-grouping;
    }
  }

  grouping bgp-grouping {
    leaf as-number {
      type uint16;
    }
    container route-reflector {
      uses bgp-routers-grouping;
      description
        "On each device in the routers list, a VPNv4 (and optional VPNv6)
         neighbour will be configured for each router in provider‑edge/routers
         list, and a link-state neighbour will be configured for each router in
         the link‑state/routers list.";
    }
    container provider-edge {
      uses bgp-routers-grouping;
      description
        "On each device in the routers list, a VPNv4 (and optional VPNv6)
         neighbour will be configured to each router in the
         route‑reflector/routers list.";
      list family {
        key name;
        leaf name {
          type enumeration {
            enum l2vpn;
            enum ip;
            enum mvpn;
          }
        }
        container policy {
          leaf name {
            type string;
          }
          leaf direction {
            type enumeration {
              enum in;
              enum out;
            }
          }
          leaf value {
            type string;
          }
        }
      }
    }
    container customer-edge {
      list vrf {
        key name;
        leaf name {
          type string;
        }
        leaf address-family {
          type enumeration {
            enum ipv4;
            enum ipv6;
          }
        }
        leaf vlan-id {
          type uint16;
        }
        list router {
          key name;
          leaf name {
            type string;
            tailf:non-strict-leafref {
              path "deref(../../../../topology)/../devices/device/device-name";
            }
          }
          choice address-family {
            leaf ipv4-address-start {
              type tailf:octet-list {
                tailf:value-length 3;
              }
              when "../../address-family='ipv4'";
            }
            leaf ipv6-address-start {
              type hexadectet-list {
                pattern '.*(:.*){0,4}';
              }
              when "../../address-family='ipv6'";
            }
          }
        }
      }
    }
    container link-state {
      uses bgp-routers-grouping;
      description
        "On each device in the routers list, a link-state neighbour will be
         configured to each router in the route‑reflector/routers list.";
    }
    container networks {
      list network {
        key "device interface-type interface-id";
        leaf device {
          type string;
          tailf:non-strict-leafref {
            path "deref(../../../topology)/../devices/device/device-name";
          }
        }
        leaf interface-type {
          type enumeration {
            enum GigabitEthernet;
            enum Loopback;
          }
        }
        leaf interface-id {
          type uint8;
        }
      }
    }
  }
}
