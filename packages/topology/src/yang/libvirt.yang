submodule libvirt {

  yang-version 1.1;

  belongs-to topology {
    prefix topology;
  }

  import ietf-yang-types {
     prefix yang;
  }
  import ietf-inet-types {
    prefix inet;
  }
  import tailf-common {
    prefix tailf;
  }
  import tailf-ncs {
    prefix ncs;
  }
  import tailf-ncs-ned {
    prefix ned;
  }

  description
    "This submodule contains the libvirt models for hypervisors and device
     defintions (used to define a domain on libvirt).";

  grouping libvirt-get-network-grouping {
    leaf name {
      type string;
    }
    list interface {
      leaf domain-name {
        type string;
      }
      leaf host-interface {
        type string;
      }
      leaf mac-address {
        type string;
      }
    }
  }

  grouping libvirt-hypervisor-grouping {
    container libvirt {
      list hypervisor {
        key name;
        description
         "Connection and management information for the hypervisor.
          Libvirt must be installed on this host.";
        leaf name {
          type string;
        }
        leaf host {
          type string;
          tailf:info
            "Used with transport leaf to generate the libvirt connection URI.";
        }
        leaf transport {
          type enumeration {
            enum "tls";
            enum "tcp";
            enum "ssh";
            enum "libssh";
            enum "unix";
          }
          default "ssh";
          description
            "Refer to the libvirt connection URI documentation for
             information about each transport type.";
        }
        leaf username {
          type string;
          description
            "These credentials will be returned by the authentication callback
             used by libvirt. Note: the SSH transport type does not support
             password authentication and must use SSH keys for passwordless
             authentication.";
        }
        leaf password {
          type tailf:aes-256-cfb-128-encrypted-string;
        }
        container tls {
          presence true;
          leaf client-certificate {
            type string;
            tailf:info "Path to the client certificate file.";
          }
          leaf client-key {
            type string;
            tailf:info "Path to the client key file.";
          }
        }
        container management-network {
          leaf bridge {
            type string;
            default 'l3v1';
            tailf:info "This bridge must exist on the libvirt host.";
            description
              "The first interface of each device will be attached to this
               bridge.";
          }
          leaf ip-address-start {
            type inet:ipv4-address;
            default '198.18.1.60';
            tailf:info
              "Added to the device ID to generate the management IP address.";
          }
          leaf gateway-address {
            type inet:ipv4-address;
            default '198.18.1.1';
            tailf:info "To be used in day0-file templates.";
            description
              "This leaf can be referenced in day0-file templates to create
               static routes to ensure NSO can reach the device once it has
               booted.";
          }
          leaf dns-server-address {
            type inet:ipv4-address;
            default '198.18.133.1';
            tailf:info "To be used in day0-file templates.";
          }
        }
        leaf mac-address-start {
          type yang:hex-string {
            tailf:value-length 3;
          }
          default '02:c1:5c';
          tailf:info "All generated MAC addresses will start with this value.";
        }
        leaf external-bridge {
          type string;
          default 'l2v1';
          tailf:info
            "Default external bridge for links to devices on another host.";
        }
        leaf udp-tunnel-ip-address {
          type inet:ipv4-address;
          default '0.0.0.0';
        }
        leaf geneve-tunnel-ip-address {
          type inet:ipv4-address;
          default '0.0.0.0';
          description
            "Source IP for GENEVE overlay tunnels. When set (non-zero), used
             for cross-hypervisor container links that do not specify an external bridge.";
        }

        container get {
          description
            "These actions retrieve the current live configuration from the
             hypervisor, regardless of any topologies defined in NSO.";
          action domains {
            tailf:actionpoint libvirt-get-objects;
            output {
              list domain {
                leaf name {
                  type string;
                }
                leaf vcpus {
                  type uint16;
                }
                leaf memory {
                  type uint16;
                }
                leaf active {
                  type boolean;
                }
              }
            }
          }

          action networks {
            tailf:actionpoint libvirt-get-objects;
            output {
              list network {
                uses libvirt-get-network-grouping;
                leaf bridge-name {
                  type string;
                }
              }
              list external-bridge {
                uses libvirt-get-network-grouping;
                description
                  "Any host bridges used directly by domains with no network
                   configured in libvirt i.e. the management bridge.";
              }
            }
          }

          action volumes {
            tailf:actionpoint libvirt-get-objects;
            output {
              list storage-pool {
                leaf name {
                  type string;
                }
                list volume {
                  leaf name {
                    type string;
                  }
                  leaf capacity {
                    type uint32;
                  }
                  leaf allocation {
                    type uint32;
                    description "Storage currently used.";
                  }
                }
              }
            }
          }

          action containers {
            tailf:actionpoint libvirt-get-objects;
            output {
              list container {
                leaf name {
                  type string;
                }
                leaf status {
                  type string;
                }
              }
            }
          }

          action container-networks {
            tailf:actionpoint libvirt-get-objects;
            output {
              list veth-pair {
                list interface {
                  leaf name {
                    type string;
                  }
                  leaf container {
                    type string;
                  }
                  leaf bridge {
                    type string;
                  }
                }
              }
              list network {
                leaf name {
                  type string;
                }
                list container {
                  leaf name {
                    type string;
                  }
                }
              }
              list tap-interface {
                leaf name {
                  type string;
                }
                leaf mac-address {
                  type string;
                }
                leaf bridge {
                  type string;
                }
                leaf container {
                  type string;
                }
              }
            }
          }
        }
      }

      list device-definition {
        key name;
        description "Parameters for defining a device in libvirt.";
        leaf name {
          type string;
        }
        leaf device-type {
          type enumeration {
            enum XRv-9000 {
              tailf:info "ISO image for day 0. Two extra management interfaces.";
            }
            enum VXR-8000 {
              tailf:info "ISO image for day 0. Two extra management interfaces.";
            }
            enum vJunos-Evolved {
              tailf:info "USB image for day 0. Four extra management interfaces.";
            }
            enum IOSv {
              tailf:info "FAT disk image for day 0.";
            }
            enum vMX {
              tailf:info "FAT disk image for day 0. Extra int network CP to FP.";
            }
            enum Linux {
              tailf:info "ISO image using cloud-init for day 0.";
            }
            enum XRd {
              tailf:info "Base image is Docker image";
            }
            enum SR-Linux {
              tailf:info "Base image is Docker image";
            }
            enum Catalyst-8000V {
              tailf:info "ISO image for day 0.";
            }
          }
          mandatory true;
          description
            "Determines how to generate the day 0 image and any other
             configuration required for the device.";
        }
        leaf vcpus {
          type uint16;
        }
        leaf memory {
          type uint16;
        }
        leaf template {
          when "../device-type!='XRd' and ../device-type !='SR-Linux'";
          type string;
          mandatory true;
          description
            "The name of the libvirt XML template file. Disk and interfaces are
             automatically added when a device is defined.";
           tailf:info
             "Libvirt XML file (omitting .xml) present in the images directory.";
        }
        leaf storage-pool {
          type string;
          mandatory true;
          tailf:info
            "Disk and day 0 image for each device are created in this pool.";
        }
        leaf base-image {
          type string;
          mandatory true;
          tailf:info
            "Image name (Docker); full path (VXR); volume name (Libvirt)";
          description
            "For Libvirt, this file must exist in the storage-pool.
             For VXR, this must be the full path to the image file.
             For Docker, this must be the name of existing an loaded image.";
        }
        leaf base-image-type {
          when "../device-type!='XRd' and ../device-type!='SR-Linux' and ../device-type!='VXR-8000'";
          type enumeration {
            enum backing-store {
              tailf:info "Use for qcow2 images only";
            }
            enum clone {
              tailf:info
                "A full clone of the base-image is created for each device.";
            }
          }
          default backing-store;
        }
        leaf disk-size {
          type uint16;
        }
        leaf day0-file {
          type string;
          tailf:info
            "Template in the images directory. If empty, no day 0 is used.";
        }
        leaf day0-upload-file {
          type string;
          description
            "The contents of this file are base64 encoded into the file-content
             attribute to use in day 0 templates.";
        }
        leaf authgroup {
          type leafref {
            path "/ncs:devices/ncs:authgroups/ncs:group/ncs:name";
          }
          mandatory true;
        }
        leaf ned-id {
          type union {
            type identityref {
              base ned:cli-ned-id;
            }
            type identityref {
              base ned:netconf-ned-id;
            }
          }
          tailf:info
            "Device will be created and synced in NSO using this ned-id.";
        }
        leaf-list capabilities {
          when "../ned-id";
          tailf:non-strict-leafref {
            path "/ncs:devices/ncs:ned-ids"
               + "/ncs:ned-id[ncs:id = current()/../ned-id]/ncs:module/ncs:name";
          }
          type string;
          tailf:info
            "List of capabilities to add to southbound-locked devices.";
        }
        leaf console-monitor {
          type boolean;
          tailf:info "Enable console monitoring (will block telnet port).";
          default false;
        }
        leaf console-timeout {
          type uint32;
          tailf:info "Maximum seconds with no console activity.";
          default 300;
        }
      }
    }
  }
}
