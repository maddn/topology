submodule traffic-generator {
  yang-version 1.1;
  belongs-to topology { prefix topology; }

  import tailf-common { prefix tailf; }
  import tailf-ncs { prefix ncs; }

  grouping traffic-generator-service-grouping {
    list traffic-generator {
      key topology;
      leaf topology {
        type leafref {
          path "/topologies/topology/name";
        }
      }

      uses ncs:service-data;
      ncs:servicepoint traffic-generator;

      uses traffic-generator-grouping;
    }
  }

  grouping traffic-generator-grouping {
    leaf-list devices {
      type string;
      tailf:non-strict-leafref {
        path "deref(../topology)/../devices/device/device-name";
      }
    }
    leaf-list destinations {
      type tailf:octet-list {
        tailf:value-length 2;
      }
    }
  }
}
