submodule topology-ui {
  yang-version 1.1;
  belongs-to topology { prefix topology; }

  import tailf-ncs {
    prefix ncs;
  }
  import tailf-common {
    prefix tailf;
  }

  description
    "This submodule contains the libvirt extensions to the topology model.";

  typedef icon-type {
    type enumeration {
      enum "antenna";
      enum "cpe";
      enum "customer-router";
      enum "firewall";
      enum "generic";
      enum "load-balancer";
      enum "probe";
      enum "router";
      enum "service-chain";
      enum "switch";
      enum "web-server";
    }
  }

  typedef icon-coordinate {
    type decimal64 {
      fraction-digits 18;
      range "0 .. 1";
    }
    description "Normalized relative coordinate";
  }

  typedef config-format {
    type enumeration {
      enum cli;
      enum curly-braces;
      enum json;
      enum xml;
      enum yaml;
    }
  }

  grouping get-configuration-action-grouping {
    tailf:action get-configuration {
      tailf:info "Get full device configuration";
      tailf:actionpoint get-device-configuration;

      input {
        leaf format {
          type config-format;
        }

        leaf service-meta-data {
          type boolean;
        }
      }

      output {
        leaf format {
          type config-format;
        }

        leaf config {
          type string;
        }
      }
    }
  }

  typedef background-offset {
    type enumeration {
      enum odd;
      enum even;
      enum none;
    }
  }

  grouping icon-coordinates {
    container coord {
      leaf x {
        type icon-coordinate;
      }

      leaf y {
        type icon-coordinate;
      }
    }
  }

  grouping topology-icon-grouping {
    container icon {
      leaf type {
        type icon-type;
      }

      uses icon-coordinates;

      list zoomed {
        key container;

        leaf container {
          type leafref {
            path "../../../../../layout/container/name";
          }
        }

        uses icon-coordinates;
      }

      leaf underlay {
        type boolean;
      }
    }
  }

  grouping topology-device-ui-grouping {
    leaf container {
      type leafref {
        path "../../../layout/container/name";
      }
    }

    uses topology-icon-grouping;
  }

  grouping topology-layout-grouping {
    container layout {
      leaf background-offset {
        type background-offset;
      }

      list container {
        key name;
        ordered-by user;

        leaf name {
          type string;
        }

        leaf title {
          type string;
        }

        leaf width {
          type uint8 {
            range "0..100";
          }
          must "sum(../../container/width) = 100" {
            error-message "The container widths must add up to 100%";
          }
        }

        leaf connection-colour {
          type string;
        }

        container zoomed {
          list container {
            key title;
            ordered-by user;

            leaf title {
              type string;
            }

            leaf width {
              type uint8 {
                range "0..100";
              }
              must "sum(../../container/width) = 100" {
                error-message
                  "The zoomed container widths must add up to 100%";
              }
            }
          }
        }
      }
    }
  }

  augment "/ncs:devices/ncs:device" {
    uses get-configuration-action-grouping;
  }

}
