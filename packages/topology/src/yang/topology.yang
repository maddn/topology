module topology {
  yang-version 1.1;
  namespace "http://example.com/topology";
  prefix topology;

  import tailf-common { prefix tailf; }
  import tailf-ncs { prefix ncs; }

  include common-topology;
  include common-topology-ui;
  include topology-base;
  include topology-libvirt;
  include topology-libvirt-subgroupings;
  include libvirt;
  include ip-connectivity;
  include base-config;
  include igp;
  include bgp;
  include mpls;
  include segment-routing;
  include traffic-generator;
  include managed-topology-nano-plan;

  description
    "This module includes the topology model, libvirt extensions and models
     for each network service. These are each defined in seperate submodules
     and used in the topologies container below. This module also defines the
     managed-topology model which uses the groupings from each network service
     submodule";

  grouping hidden-topology-link {
    leaf topology {
      type leafref {
        path "/topologies/topology/name";
      }
      tailf:link "/topologies/topology[name=current()/../../topology]/name";
      tailf:hidden full;
      config false;
    }
  }

  container topologies {
    uses topology-libvirt-grouping;
    uses libvirt-hypervisor-grouping;
    uses base-config-service-grouping;
    uses igp-service-grouping;
    uses bgp-service-grouping;
    uses mpls-service-grouping;
    uses segment-routing-service-grouping;
    uses traffic-generator-service-grouping;
    uses managed-topology;
  }

  augment "/topologies/topology" {
    uses ip-connectivity-service-grouping;
  }

  augment "/ncs:devices/ncs:device" {
    uses get-configuration-action-grouping;
  }

  grouping managed-topology {
    list managed-topology {
      key topology;

      ncs:servicepoint managed-topology;
      uses ncs:service-data;
      uses ncs:nano-plan-data;

      uses ip-connectivity-grouping;
      uses base-config-grouping;

      list igp {
        key name;
        uses hidden-topology-link;
        uses igp-grouping;
      }
      list bgp {
        key as-number;
        uses hidden-topology-link;
        uses bgp-grouping;
      }
      list mpls {
        key igp;
        uses mpls-grouping;
      }
      list segment-routing {
        key igp;
        uses segment-routing-grouping;
      }
      container traffic-generator {
        uses hidden-topology-link;
        uses traffic-generator-grouping;
      }
    }
  }

}
