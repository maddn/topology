submodule mpls {
  yang-version 1.1;
  belongs-to topology { prefix topology; }

  import tailf-common { prefix tailf; }
  import tailf-ncs { prefix ncs; }

  description
    "This submodule contains the MPLS service which will configure MPLS on the
     devices in the IGP domain.";

  grouping mpls-service-grouping {
    list mpls {
      key igp;

      uses ncs:service-data;
      ncs:servicepoint mpls;

      uses mpls-grouping;
    }
  }

  grouping mpls-grouping {
    leaf igp {
      type leafref {
        path "../../igp/name";
      }
    }

    leaf ldp {
      type empty;
      tailf:info
        "Enable LDP on each interface connected to another device in the IGP.";
    }
    leaf rsvp {
      type empty;
      tailf:info
        "Enable RSVP on each interface connected to another device in the IGP.";
    }
    leaf oam {
      type empty;
      tailf:info "Enabled MPLS OAM.";
    }
    container traffic-engineering {
      presence true;
      tailf:info
        "Enable TE on each interface connected to another device in the IGP.";
      container pce {
        presence true;
        tailf:info "Configure the PCE peer from the base-config service.";
        list precedence {
          key peer;
          leaf peer {
            type leafref {
              path "/topologies/base-config/pce/routers";
            }
          }
          leaf value {
            type uint8;
          }
        }

        leaf loopback-id {
          type uint8;
        }
      }
    }
  }
}
