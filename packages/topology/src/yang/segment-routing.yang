submodule segment-routing {
  yang-version 1.1;
  belongs-to topology { prefix topology; }

  import tailf-common { prefix tailf; }
  import tailf-ncs { prefix ncs; }

  description
    "This submodule contains the segment-routing service which can enable
     various segment routing features on the devices in the IGP domain.";

  typedef sid {
    type uint32 {
      range "16000..1048575";
    }
  }
  typedef hexadectet {
    type string {
      length "0..4";
      pattern "[0-9a-fA-F]*";
    }
  }
  typedef flex-algo {
    type uint8 {
      range "128..255";
    }
  }

  grouping segment-routing-service-grouping {
    list segment-routing {
      tailf:sort-priority 1000;
      key igp;

      uses ncs:service-data;
      ncs:servicepoint segment-routing;

      uses segment-routing-grouping;
    }
  }

  grouping segment-routing-grouping {
    leaf igp {
      type leafref {
        path "../../igp/name";
      }
    }

    container srgb {
      tailf:info "Segement Routing Global Block.";
      description "These bounds are used to configure the SRGB on each router";
      leaf lower-bound {
        type sid;
        default 16000;
      }
      leaf upper-bound {
        type sid;
        default 23999;
      }
    }

    leaf prefix-sid-start {
      type sid;
      default 16000;
      tailf:info
        "This value is added to the device ID to calculate the prefix-sid";
    }
    leaf prefix-sid-strict-spf-start {
      type sid;
      default 17000;
      tailf:info
        "Same as prefix-sid-start, but calculates strict-spf";
    }
    container pce {
      presence true;
      tailf:info "Configure the PCE peer from the base-config service.";
      list precedence {
        key peer;
        leaf peer {
          type leafref {
            path "/topologies/base-config/pce/routers";
          }
        }
        leaf value {
          type uint8;
        }
      }
    }
    leaf autoroute-profile-id {
      type uint32;
    }

    leaf set-link-affinity {
      type empty;
      tailf:info "Set affinity values on link interfaces";
    }

    list flex-algo {
      key id;
      description
        "Create flex-algo including prefix-sid-algorithm on the primary
         loopback interface and flex-algo affinity on each link interface.";
      leaf id {
        type flex-algo;
      }
      leaf metric-type-delay {
        type empty;
      }
      leaf affinity-exclude {
        type leafref {
          path "/topologies/topology/links/link/affinity";
        }
      }
      leaf srv6-locator {
        when "../../srv6";
        type string;
        tailf:info "Create an SRv6 locator for the flex-algo";
      }
      leaf-list devices {
        type string;
        tailf:non-strict-leafref {
          path "/topologies/topology/devices/device/device-name";
        }
        tailf:info "Only create flex-algo on these devices else all IGP devices.";
      }
    }

    container srv6 {
      when "deref(deref(../igp)/../topology)/../ip-connectivity/ipv6" {
        tailf:dependency "/topologies/topology/ip-connectivity/ipv6";
      }
      presence true;
      leaf locator-prefix-start {
        type hexadectet;
        default "fcbb";
      }
    }
  }

}
