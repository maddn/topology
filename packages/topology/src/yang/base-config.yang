submodule base-config {
  yang-version 1.1;
  belongs-to topology { prefix topology; }

  import ietf-inet-types { prefix inet; }
  import tailf-common { prefix tailf; }
  import tailf-ncs { prefix ncs; }

  description
    "This submodule contains the base-config service which configures each
     device in the topology with common standalone features typically found in
     a golden config. This service can also configure static routes between
     devices in the topology.";

  grouping base-config-service-grouping {
    list base-config {
      key topology;

      uses ncs:service-data;
      ncs:servicepoint base-config;

      uses base-config-grouping;
    }
  }

  grouping base-config-grouping {
    leaf topology {
      type leafref {
        path "/topologies/topology/name";
      }
    }
    leaf login-banner {
      type string;
      tailf:info
        "This login-banner will be configured on every device in the topology.";
    }

    container logging {
      presence true;
      tailf:info "Configures some default logging parameters on each device.";
      container syslog-server {
        leaf ip-address {
          type inet:ipv4-address;
        }
        leaf port {
          type inet:port-number;
        }
      }
      leaf console {
        type enumeration {
          enum disable;
          enum debugging;
          enum error;
          enum notifications;
          enum warning;
        }
        default notifications;
      }
    }

    leaf ntp-server {
      type inet:ipv4-address;
    }

    container snmp-server {
      presence true;
      list host {
        key ip-address;
        leaf ip-address {
          type inet:ipv4-address;
        }
        leaf port {
          type inet:port-number;
        }
        leaf community-string {
          type string;
        }
      }
    }

    container grpc {
      presence true;
      leaf port {
        type inet:port-number;
      }
    }

    leaf interface-bandwidth {
      type uint32;
      tailf:info "Bandwidth for every topology link and network interface.";
    }

    container static-routes {
      list route {
        key "source-device destination-device loopback-id";
        description
          "Configure a static route to the loopback address of a directly
           connected device, and a optionally a return route on the
           destination-device.";
        leaf source-device {
          type string;
          tailf:non-strict-leafref {
            path "deref(../../../topology)/../devices/device/device-name";
          }
          tailf:info "The device the route will be configured on.";
        }
        leaf destination-device {
          type string;
          tailf:non-strict-leafref {
            path "deref(../../../topology)/../devices/device/device-name";
          }
          must "count(deref(../../../topology)/../links/" +
                     "link[a-end-device=current()]" +
                         "[z-end-device=current()/../source-device]) + " +
               "count(deref(../../../topology)/../links/" +
                     "link[z-end-device=current()]" +
                         "[a-end-device=current()/../source-device]) = 1" {
            tailf:dependency "../source-device";
            tailf:dependency "../../../../topology/links/link";
            error-message "source-device and destination-device must be " +
              "directly connect (with an entry in the topology links list.)";
          }
          description
            "The next hop is automatically looked up from the topology links.";
        }
        leaf loopback-id {
          type uint8;
          tailf:non-strict-leafref {
            path "deref(../../../topology)/.." +
                 "/ip-connectivity/loopback-interfaces/loopback/id";
          }
        }
        leaf return-route {
          tailf:info "Create a return route on the destination-device.";
          type enumeration {
            enum source-device {
              tailf:info
                "Create a return route to the source loopback address.";
            }
            enum source-subnet {
              tailf:info
                "Create a return route to the source loopback subnet.";
            }
            enum none;
          }
          default source-subnet;
        }
        leaf redistribute-link {
          type empty;
        }
        leaf add-links-subnet {
          type empty;
        }
      }

      container loopback-to-management {
        leaf device {
          type string;
          tailf:non-strict-leafref {
            path "deref(../../../topology)/../devices/device/device-name";
          }
          description
            "Create routes on this device from the loopback to management
             address of each device in the topology;";
        }
        leaf loopback-id {
          type uint8;
          tailf:non-strict-leafref {
            path "deref(../../../topology)/.." +
                 "/ip-connectivity/loopback-interfaces/loopback/id";
          }
        }
      }
    }

    leaf multicast {
      type empty;
    }

    container pce {
      leaf-list routers {
        type string;
        tailf:non-strict-leafref {
          path "/topologies/topology/devices/device/device-name";
        }
      }
      leaf loopback-id {
        type uint8;
      }
      leaf password {
        type string;
      }
      container p2mp {
        presence true;
        leaf min-label {
          type uint32 {
            range "16..1048575";
          }
        }
        leaf max-label {
          type uint32 {
            range "16..1048575";
          }
        }
      }
    }

    container customer-networks {
      list interface {
        key "device interface ipv4-subnet-start";
        leaf device {
          type string;
          tailf:non-strict-leafref {
            path "deref(../../../topology)/../devices/device/device-name";
          }
        }
        leaf interface {
          type uint8;
        }
        leaf ipv4-subnet-start {
          type tailf:octet-list {
            tailf:value-length 3;
          }
        }
      }
    }
  }
}
