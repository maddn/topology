submodule topology-libvirt {
  yang-version 1.1;
  belongs-to topology { prefix topology; }

  import tailf-common { prefix tailf; }

  include topology-base;

  // Additional groupings are in a seperate submodule due to an NSO bug.
  // If the groupings are in the same submodule they are missing from the
  // compiled module.
  include topology-libvirt-subgroupings;

  description
    "This submodule contains the libvirt extensions to the topology model.";

  grouping topology-libvirt-grouping {
    description
      "This grouping refines and augments the topology-base-grouping so the
       topology model can be used with libvirt.";
    uses topology-base-grouping {
      refine "topology/devices/device/container" {
        tailf:default-ref "../hypervisor";
      }

      augment "topology/links/link/a-end-interface" {
        uses libvirt-interface-grouping;
      }
      augment "topology/links/link/z-end-interface" {
        uses libvirt-interface-grouping;
      }
      augment "topology/links/link" {
        container external-connection {
          /*when
            "not(deref(../a-end-device)/../hypervisor = " +
                "deref(../z-end-device)/../hypervisor or " +
                "not(deref(../a-end-device)/../hypervisor) and " +
                "not(deref(../z-end-device)/../hypervisor) or " +
                "not(deref(../z-end-device)/../hypervisor) and " +
                  "deref(../a-end-device)/../hypervisor = " +
                  "../../../libvirt/hypervisor or " +
                "not(deref(../a-end-device)/../hypervisor) and " +
                  "deref(../z-end-device)/../hypervisor = " +
                  "../../../libvirt/hypervisor)" {
            tailf:dependency "/topologies/topology/libvirt/hypervisor";
            tailf:dependency "/topologies/topology/devices/device/hypevisor";
          }*/
          tailf:info
            "Link spans two hypervisors and connected using existing bridges.";
          description
            "The interfaces on this link will be connected to existing bridges
             given here, or the default external-bridge for the hypervisor.";
          leaf a-end-bridge {
            type string;
          }
          leaf z-end-bridge {
            type string;
          }
        }
        container libvirt {
          action start {
            tailf:actionpoint libvirt-network-action;
            output {
              uses libvirt-action-output-grouping;
            }
          }
          action stop {
            tailf:actionpoint libvirt-network-action;
            output {
              uses libvirt-action-output-grouping;
            }
          }
          action update {
            tailf:actionpoint libvirt-network-action;
            output {
              uses libvirt-action-output-grouping;
            }
          }
          action set-delay {
            tailf:actionpoint libvirt-network-action;
            input {
              leaf delay {
                type int32;
              }
            }
            output {
              uses libvirt-action-output-grouping;
            }
          }
          leaf delay {
            type int32;
          }
        }
      }

      augment "topology/networks/network/devices/device/interface" {
        uses libvirt-interface-grouping;
      }

      augment "topology" {
        container libvirt {
          leaf hypervisor {
            type leafref {
              path "/topologies/libvirt/hypervisor/name";
            }
            description "The default hypervisor the topology will run on";
          }
          action define {
            tailf:actionpoint libvirt-action;
            description
              "Convert the topology devices, links and networks into libvirt
               XML for corresponding domains, storage and networks and push to
               the hypervisor.";
            input {
              uses libvirt-action-input-grouping;
            }
            output {
              uses libvirt-action-output-grouping;
            }
          }
          action undefine {
            tailf:actionpoint libvirt-action;
            description
              "Undefine the corresponding domains, volumes and networks for
               this topology on the hypervisor.";
            input {
              uses libvirt-action-input-grouping;
            }
            output {
              uses libvirt-action-output-grouping;
            }
          }
          action start {
            tailf:actionpoint libvirt-action;
            description
              "Start the corresponding domains, volumes and networks for this
               topology on the hypervisor.";
            input {
              uses libvirt-action-input-grouping;
            }
            output {
              uses libvirt-action-output-grouping;
            }
          }
          action stop {
            tailf:actionpoint libvirt-action;
            description
              "Stop the corresponding domains, volumes and networks for this
               topology on the hypervisor.";
            input {
              uses libvirt-action-input-grouping;
            }
            output {
              uses libvirt-action-output-grouping;
            }
          }
          action reboot {
            tailf:actionpoint libvirt-action;
            description
              "Stop and restart the chosen domain.";
            input {
              uses libvirt-action-input-grouping;
            }
            output {
              uses libvirt-action-output-grouping;
            }
          }
          action hard-reset {
            tailf:actionpoint libvirt-action;
            description
              "Stop, undefine, redefine and restart the chosen domain.";
            input {
              uses libvirt-action-input-grouping;
            }
            output {
              uses libvirt-action-output-grouping;
            }
          }
        }

        container state-events {
          config false;
          tailf:cdb-oper {
            tailf:persistent true;
          }
          list event {
            leaf timestamp {
              type string;
            }
            leaf device {
              type leafref {
                path "../../../devices/device/device-name";
              }
            }
            leaf event-type {
              type enumeration {
                enum online;
                enum offline;
                enum warn;
              }
            }
            leaf ping-missed-packets {
              type string;
            }
          }
        }

        container operational-state-monitor {
          action start {
            tailf:actionpoint operational-state-monitor;
          }
          action stop {
            tailf:actionpoint operational-state-monitor;
          }
          action clear {
            tailf:actionpoint operational-state-monitor;
          }
          action status {
            tailf:actionpoint operational-state-monitor;
            output {
              leaf status {
                type enumeration {
                  enum running;
                  enum not-running;
                }
              }
              leaf process-pid {
                type uint32;
              }
            }
          }
        }

        action check-topology-status {
          tailf:actionpoint check-topology-status;
          description
            "Checks if the topology devices are reachable, and synchronizes
             them into NSO. Updates the device and topology status leaves.";
          input {
            leaf frequency {
              type enumeration {
                enum run-now {
                  tailf:info "Run once immediately";
                }
                enum schedule {
                  tailf:info "Run every 2 minutes until all devices are ready.";
                }
              }
              default run-now;
            }
          }
          output {
            list device {
              leaf name {
                type string;
              }
              leaf status {
                type provisioning-status;
              }
            }
          }
        }
        leaf provisioning-status {
          type provisioning-status;
          default undefined;
          config false;
          tailf:cdb-oper {
            tailf:persistent true;
          }
          description "Updated by the check-topology-status action.";
        }
      }

      augment "topology/links/link" {
        uses libvirt-network-grouping;
      }
      augment "topology/networks/network" {
        uses libvirt-network-grouping;
        leaf external-bridge {
          type string;
          tailf:info
            "Use this pre-existing bridge instead of creating a new network.";
        }
      }
      augment "topology/devices/device" {
        uses libvirt-device-grouping;
      }
    }
  }
}
