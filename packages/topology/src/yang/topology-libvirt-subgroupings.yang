submodule topology-libvirt-subgroupings {
  yang-version 1.1;
  belongs-to topology { prefix topology; }

  import ietf-yang-types { prefix yang; }
  import ietf-inet-types { prefix inet; }
  import tailf-common { prefix tailf; }

  typedef provisioning-status {
    type enumeration {
      enum undefined;
      enum defined;
      enum started;
      enum stopping;
      enum ready;
      enum sync-error;
      enum unmanaged;
    }
  }

  typedef operational-status {
    type enumeration {
      enum reachable;
      enum not-reachable;
    }
  }

  grouping libvirt-action-input-grouping {
    leaf force {
      type boolean;
      tailf:info
        "Run the action even if the topology is not in the expected state.";
    }
    leaf device {
      type string;
      tailf:non-strict-leafref {
        path "../../../devices/device/device-name";
      }
      tailf:info "Only run the action on a single device.";
    }
  }

  grouping libvirt-action-output-grouping {
    list libvirt-action {
      leaf action {
        type string;
      }
      list hypervisor {
        key name;
        leaf name {
          type string;
        }
        leaf-list networks {
          type string;
        }
        leaf-list domains {
          type string;
        }
        leaf-list volumes {
          type string;
        }
      }
    }
  }

  grouping libvirt-network-grouping {
    leaf host-bridge {
      type string;
      config false;
      tailf:cdb-oper {
        tailf:persistent true;
      }
    }
    leaf mac-address {
      type yang:mac-address;
      config false;
      tailf:cdb-oper {
        tailf:persistent true;
      }
    }
  }

  grouping libvirt-interface-grouping {
    leaf host-interface {
      type string;
      config false;
      tailf:cdb-oper {
        tailf:persistent true;
      }
    }
    leaf mac-address {
      type yang:mac-address;
      config false;
      tailf:cdb-oper {
        tailf:persistent true;
      }
    }
    leaf ip-address {
      type inet:ipv4-address;
      config false;
      tailf:cdb-oper {
        tailf:persistent true;
      }
    }
  }

  grouping libvirt-device-grouping {
    leaf definition {
      type leafref {
        path "/topologies/libvirt/device-definition/name";
      }
    }
    container management-interface {
      config false;
      tailf:cdb-oper {
        tailf:persistent true;
      }
      leaf ip-address {
        type inet:ipv4-address;
      }
      leaf mac-address {
        type yang:mac-address;
      }
      leaf host-interface {
        type string;
      }
    }
    leaf provisioning-status {
      type provisioning-status;
      default undefined;
      config false;
      tailf:cdb-oper {
        tailf:persistent true;
      }
      description "Updated by the check-topology-status action.";
    }
    leaf operational-status {
      type operational-status;
      default not-reachable;
      config false;
      tailf:cdb-oper {
        tailf:persistent true;
      }
    }
    leaf hypervisor {
      type leafref {
        path "/topologies/libvirt/hypervisor/name";
      }
      description
        "Hypervisor the device will run on, if different to the default";
    }
    container console {
      config false;
      tailf:cdb-oper {
        tailf:persistent true;
      }
      leaf last-activity {
        type string;
      }
      leaf last-message {
        type string;
        tailf:cli-value-display-template "$(.|trunc:100)";
      }

      action start {
        tailf:actionpoint console-activity-monitor;
      }
      action stop {
        tailf:actionpoint console-activity-monitor;
      }
      action status {
        tailf:actionpoint console-activity-monitor;
        output {
          leaf status {
            type enumeration {
              enum running;
              enum not-running;
            }
          }
          leaf process-pid {
            type uint32;
          }
        }
      }
    }

  }

}
