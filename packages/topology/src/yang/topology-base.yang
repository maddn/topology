submodule topology-base {
  yang-version 1.1;
  belongs-to topology { prefix topology; }

  import tailf-common { prefix tailf; }

  include common-topology;
  include common-topology-ui;

  description
    "This submodule defines the base topology model. It is intended that the
     model can be used on its own with the network services in this package.
     Currently this model is refined in the topology-libvirt submodule to add
     the libvirt nodes, and that is the version included in the final topology
     model.";

  grouping topology-base-grouping {
    uses topology-grouping {
      augment "topology/devices" {
        list device {
          key id;
          leaf id {
            type uint8;
            mandatory true;
            tailf:info
              "Used in device and resource names such as IP and MAC addresses.";
            description
              "Recommended to keep this value in sequence starting at 1.";
          }
          leaf prefix {
            type string;
            mandatory true;
            tailf:info "Prefixed to the ID to generate the device name.";
          }
          leaf device-name {
            type string;
            config false;
            tailf:callpoint device-name-callpoint {
              tailf:transform true;
            }
          }
          leaf control-plane-id {
            type leafref {
              path "../../device/id";
            }
            tailf:info
              "ID of device to actually configure when the CP is seperate.";
          }

          uses topology-device-ui-grouping;
        }
      }

      augment "topology/links/link" {
        container a-end-interface {
          leaf id {
            type uint8;
            must "count(../../../link[a-end-device=current()/../.." +
                       "/a-end-device]/a-end-interface[id=current()]) + " +
                 "count(../../../link[z-end-device=current()/../.." +
                       "/a-end-device]/z-end-interface[id=current()]) + " +
                 "count(../../../../networks/network[interface-id=current()]" +
                       "/devices/device[name=current()/../../a-end-device])" +
                 "<= 1" {
              error-message
                "A device interface can only be used in 1 link or network";
            }
          }
        }

        container z-end-interface {
          leaf id {
            type uint8;
            must "count(../../../link[a-end-device=current()/../.." +
                       "/z-end-device]/a-end-interface[id=current()]) + " +
                 "count(../../../link[z-end-device=current()/../.." +
                       "/z-end-device]/z-end-interface[id=current()]) + " +
                 "count(../../../../networks/network[interface-id=current()]" +
                       "/devices/device[name=current()/../../z-end-device])" +
                 "<= 1" {
              error-message
                "A device interface can only be used in 1 link or network";
            }
          }
        }
        leaf igp-metric {
          type uint32;
        }
        leaf te-metric {
          type uint32;
        }
        leaf delay-metric {
          type uint32;
        }
        leaf affinity {
          type string;
        }
        leaf cdp {
          type empty;
        }
        leaf lldp {
          type empty;
        }
        leaf exclude-ip-connectivity {
          type empty;
        }
        leaf destroy-behaviour {
          type enumeration {
            enum safe;
            enum immediate;
          }
          default safe;
          config false;
          description
            "Set automatically depending on the link device types";
        }
      }

      augment "topology" {
        container networks {
          description "Networks connecting multiple devices in the topology.";
          list network {
            key name;
            leaf name {
              type string;
            }
            leaf interface-id {
              type uint8;
              mandatory true;
              tailf:info
                "The same interface ID is used for each device in the network.";
            }
            leaf ipv4-subnet-start {
              type tailf:octet-list {
                tailf:value-length 3;
              }
              tailf:info
                "First three octets of the network subnet.";
              default '10.11.12';
            }
            container devices {
              description "The devices in the network.";
              list device {
                key name;
                leaf name {
                  type string;
                  tailf:non-strict-leafref {
                    path "../../../../../devices/device/device-name";
                  }
                }
                container interface {
                  leaf id {
                    type uint8;
                  }
                }
              }
            }
          }
        }

        uses topology-layout-grouping;
      }
    }
  }
}
